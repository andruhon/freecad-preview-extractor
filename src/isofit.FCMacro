# -*- coding: utf-8 -*-

# Macro Begin: isofit.FCMacro +++++++++++++++++++++++++++++++++++++++++++++++++
import FreeCAD

try:
    view = Gui.activeDocument().activeView()
    view.setAnimationEnabled(False)
    view.viewIsometric()
    Gui.SendMsgToActiveView("ViewFit")
    Gui.updateGui()
    Gui.SendMsgToActiveView("Save")
    Gui.getMainWindow().close()
except Exception as e:
    print("Error in isofit macro: {}".format(e))
    Gui.getMainWindow().close()

# Macro End: isofit.FCMacro +++++++++++++++++++++++++++++++++++++++++++++++++
